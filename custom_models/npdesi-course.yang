module npdesi-course {
    namespace "http://npdesi.cisco.com/training"; 
    prefix "npdesi";
    organization "Cisco Inc.";
    contact "chuck@npdesi.cisco.com";
    description "Here is a module used for basic switch configuration";
    revision 2017-06-07 {
        description "Initial revision";
        reference "NPDESI COURSE MODULE";
    }
    container system {
        description "System container for configuration";
        leaf hostname {
            type string;
            config true;
            description "System Host Name";
        }
        leaf-list dns-servers {
            type string;
            config true;
            ordered-by user;
            description "DNS servers";
        }
    }
    container vlans {
        description "Vlan container for defining vlans";
        list vlan {
            key vlanid;
            description "Vlans listed keyed by id";
            leaf vlanid {
                type uint16 {
                    range "1 .. 4096";
                }
                description "Vlan number 1-4096";
            }
            leaf name {
                type string;
                description "Name of vlan";
            }
        }
    }
}
